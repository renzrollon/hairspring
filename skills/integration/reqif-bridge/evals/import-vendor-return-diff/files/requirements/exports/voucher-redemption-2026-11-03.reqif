# Voucher redemption
Exported by re-lint reqif from requirements/requirements.csv

# Specification: Voucher redemption

## R-040: Issue voucher on redemption request
WHEN a member with at least 500 posted points requests a voucher in the customer mobile app, the loyalty service shall issue a voucher worth SGD 1 per 100 points redeemed.
- Type: F
- Source: S-01 (programme T&C draft v3)
- Priority: must
- Status: agreed
- Rationale: Redemption is why members collect points; the minimum and the rate are programme rules in S-01.

## R-041: Validate voucher at checkout
WHEN the POS sends a voucher validation request for a voucher in state Issued, the loyalty service shall return the voucher value to the POS.
- Type: F
- Source: S-02 (TillPoint interface spec v2.1)
- Priority: must
- Status: agreed
- Rationale: Cashiers apply a voucher only after the loyalty service has confirmed it.

## R-085: Voucher validation response time at peak
WHILE the POS load is at most 9000 purchases per minute across stores, the loyalty service shall answer 95% of voucher validation requests within 300 ms.
- Type: Q
- Source: I-02 (Arjun Pillai SH-02); peak load SH-08
- Priority: must
- Status: agreed
- Rationale: Checkout must not get slower (SH-02); 9000 purchases per minute is last year's year-end peak (SH-08).
