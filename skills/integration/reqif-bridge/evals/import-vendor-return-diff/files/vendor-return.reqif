# Voucher redemption
Reviewed by the POS vendor (SH-09), sample file.

# Specification: Voucher redemption

## R-041: Validate voucher at checkout
WHEN the POS sends a voucher validation request for a voucher in state Issued, the loyalty service shall return the voucher value and the voucher expiry date to the POS.
- Type: F
- Source: S-02 (TillPoint interface spec v2.1)
- Priority: must
- Status: agreed
- Rationale: Cashiers apply a voucher only after the loyalty service has confirmed it.
- Vendor comment: TillPoint v2.2 shows the voucher expiry on the till screen, so we need it in the response.

## R-085: Voucher validation response time at peak
WHILE the POS load is at most 9000 purchases per minute across stores, the loyalty service shall answer 95% of voucher validation requests within 300 ms.
- Type: Q
- Source: I-02 (Arjun Pillai SH-02); peak load SH-08
- Priority: must
- Status: Accepted
- Rationale: Checkout must not get slower (SH-02); 9000 purchases per minute is last year's year-end peak (SH-08).

## R3: Log voucher validation requests
The loyalty service shall log each voucher validation request with the store ID and the result.
- Type: F
- Vendor comment: Needed for our store reconciliation report.
